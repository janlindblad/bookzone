module bookzone-example {
  yang-version 1.1;
  namespace 'http://example.com/ns/bookzone';
  prefix bz;

  import ietf-yang-types {
    prefix yang;
  }

  revision 2018-01-03 {
    description 
      "Added action purchase and notification shipping.";
  }
  revision 2018-01-02 {
    description 
      "Added book formats, authors and users, see 
       /books/book/format
       /authors
       /users";
  }
  revision 2018-01-01 {
    description "Initial revision. A catalog of books.";
  }

  typedef language-type {
    type enumeration {
      enum arabic;
      enum chinese;
      enum english;
      enum french;
      enum moroccan-arabic;
      enum swahili;
      enum swedish;
      // List not exhaustive in order to save space
    }
    description 
      "Primary language the book consumer needs to master "+
      "in order to appreciate the book's content";
  }

  identity format-idty {
    description "Root identity for all book formats";
  }
  identity paper {
    base format-idty;
    description "Physical book printed on paper";
  }
  identity audio-cd {
    base format-idty;
    description "Audiobook delivered as Compact Disc";
  }
  identity file-idty {
    base format-idty;
    description "Book delivered as a file";
  }
  identity paperback {
    base paper;
    description "Physical book with soft covers";
  }
  identity hardcover {
    base paper;
    description "Physical book with hard covers";
  }
  identity mp3 {
    base file-idty;
    description "Audiobook delivered as MP3 file";
  }
  identity pdf {
    base file-idty;
    description "Digital book delivered as PDF file";
  }
  identity epub {
    base file-idty;
    description "Digital book delivered as EPUB file";
  }

  typedef ISBN-10-or-13 {
    type union {    
      type string {
        length 10;
        pattern '[0-9]{9}[0-9X]';
      }
      type string {
        length 13;
        pattern '97[89][0-9]{10}';
      }
    }
    description
      "The International Standard Book Number (ISBN) is a unique
       numeric commercial book identifier.

       An ISBN is assigned to each edition and variation (except 
       reprintings) of a book. [source: wikipedia]";
    reference 
      "https://en.wikipedia.org/wiki/International_Standard_Book_Number";
  }

  container authors {
    list author {
      key name;

      leaf name {
        type string;
      }
      leaf account-id {
        type uint32 {
          range 1001..max;
        }
      }
    }
  }

  container books {
    list book {
      key title;

      leaf title {
        type string;
      }
      leaf author {
        type leafref {
          path /authors/author/name;
        }
      }
      leaf language {
        type language-type;
      }
      list format {
        key isbn;
        leaf isbn {
          type ISBN-10-or-13;
        }
        leaf format-id {
          mandatory true;
          type identityref {
            base format-idty;
          }
        }
        leaf price {
          type decimal64 {
            fraction-digits 2;
          }
          units sim-dollar;
        }
      }
    }
  }

  container users {
    list user {
      key user-id;

      leaf user-id {
        type string;
      }
      leaf name {
        type string;
      }
      action purchase {
        input {
          leaf title {
            type leafref {
              path /books/book/title;
            }
          }
          leaf format {
            type leafref {
              path /books/book/format/format-id;
              // Reviewer note: This should be improved
            }
          }
          leaf number-of-copies {
            type uint32 {
              range 1..999;
            }
          }
        }
        output {
          choice outcome {
            case success {
              leaf success {
                type empty;
                description
                  "Order received and will be sent to specified user.
                   File orders are downloadable at the URL given below.";
              }
              leaf delivery-url {
                type string;
                description
                  "Download URL for file deliveries.";
              }
            }
            leaf out-of-stock {
              type empty;
              description
                "Order received, but cannot be delivered at this time. 
                 A notification will be sent when the item ships.";
            }
            leaf failure {
              type string;
              description
                "Order cancelled, for reason stated here.";
            }
          }
        }
      }
    }
  }
 
  notification shipping {
    leaf user {
      type leafref {
        path /users/user/name;
      }
    }
    leaf title {
      type leafref {
        path /books/book/title;
      }
    }
    leaf format {
      type leafref {
        path /books/book/format/format-id;
        // Reviewer note: This should be improved
      }
    }
    leaf number-of-copies {
      type uint32;
    }
  }
}
