module juniper-junos-nc-1.0 {
  yang-version 1.1;
  namespace "http://tail-f.com/ns/ned-id/juniper-junos-nc-1.0";
  prefix juniper-junos-nc-1.0;

  import juniper-junos-nc {
    prefix family;
  }

  identity juniper-junos-nc-1.0 {
    base family:juniper-junos-nc;
  }
}
