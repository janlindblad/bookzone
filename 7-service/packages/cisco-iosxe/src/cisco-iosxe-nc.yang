module cisco-iosxe-nc {
  yang-version 1.1;
  namespace "http://tail-f.com/ns/ned-id/cisco-iosxe-nc";
  prefix cisco-iosxe-nc;

  import tailf-common {
    prefix tailf;
  }

  import tailf-ncs-ned {
    prefix ned;
  }

  identity cisco-iosxe-nc {
    tailf:abstract;
    base ned:netconf-ned-id;
  }
}
